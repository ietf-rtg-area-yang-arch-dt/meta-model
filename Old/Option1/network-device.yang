module network-device {

  yang-version "1";

  // namespace
  namespace "urn:ietf:params:xml:ns:yang:network-device";

  prefix "struct";

  // import some basic types
  import ietf-interfaces {
    prefix if;
  }

  import ietf-ip {
    prefix ip;
  }

  // meta
  organization "IETF RTG YANG Design Team Collaboration
                with OpenConfig";

  contact
      "Routing Area YANG Architecture Design Team -
       <rtg-dt-yang-arch@ietf.org>";

  description
    "This module describes a model structure for YANG
     configuration and operational state data models. Its intent is
     to describe how individual device protocol and feature models
     fit together and interact.";

  revision "2015-09-06" {
    description
      "IETF Routing YANG Design Team Meta-Model";
    reference "TBD";
  }

  // extension statements

  // feature statements
  feature bind-network-element-id {
    description
      "Logical network element ID to which an interface is bound";
  }

  feature bind-networking-instance-name {
    description
      "Networking Instance to which an interface instance is bound";
  }

  // identity statements

  identity networking-instance {
      description
         "Base identity from which identities describing
          networking instance types are derived.";
  }

  identity oam-protocol-type {
      description
          "Base identity for derivation of OAM protocols";
  }

  identity networking-service-type {
      description
          "Base identity for derivation of networking services";
  }

   identity ethernet-protocol-type {
      description
          "Base identity for derivation of ethernet
           protocols";
   }

   identity ipv4-interface-protocol-type {
      description
          "Base identity for derivation of IPv4 interface
           protocols";
   }

   identity ipv6-interface-protocol-type {
      description
          "Base identity for derivation of IPv6 interface
           protocols";
   }

   identity mpls-protocol-type {
      description
          "Base identity for derivation of MPLS protocols";
   }

   identity control-plane-protocol-type {
      description
          "Base identity for derivation of control-plane protocols";
   }

   identity system-management-protocol-type {
      description
          "Base identity for derivation of system management
           protocols";
   }

   identity oam-service-type {
      description
          "Base identity for derivation of Operations,
           Administration, and Maintenance (OAM) services.";
   }

   identity aaa-service-type {
      description
          "Base identity for derivation of Authentication,
           Authorization, and Accounting (AAA) services.";
   }

  // typedef statements

  // grouping statements

  grouping interface-ip-common {
    description
      "interface-specific configuration for IP interfaces, IPv4 and
      IPv6";

  }

  grouping ethernet-protocols {
      description
          "Grouping for ethernet protocols configured
            on an interface";
      container ethernet-protocols {
          description
              "Container for list of ethernet protocols configured
                on an interface";
          list ethernet-protocol {
              key "type";
              description
                  "List of ethernet protocols configured
                   on an interface";
              leaf type {
                  type identityref {
                      base ethernet-protocol-type;
                  }
                  mandatory true;
                  description
                      "Aggregates, RSTP, LLDP, PTP, etc.";
              }
          }
      }
  }

  grouping ipv4-interface-protocols {
      container ipv4-interface-protocols {
          list ipv4-interface-protocol {
              key "type";
              leaf type {
                  type identityref {
                      base ipv4-interface-protocol-type;
                  }
                  mandatory true;
                  description
                      "ARP, ICMP, VRRP, DHCP Client, etc.";
              }
              description
                  "List of IPv4 protocols configured
                   on an interface";
          }
          description
              "Container for list of IPv4 protocols configured
                on an interface";
      }
      description
          "Grouping for IPv4 protocols configured on an interface";
  }

  grouping ipv6-interface-protocols {
      description
          "Grouping for IPv6 protocols configured on
           an interface.";
      container ipv6-interface-protocols {
          description
              "Container for list of IPv6 protocols configured
                on an interface.";
          list ipv6-interface-protocol {
              key "type";
              description
                  "List of IPv6 protocols configured
                   on an interface";
              leaf type {
                  type identityref {
                      base ipv6-interface-protocol-type;
                  }
                  mandatory true;
                  description
                      "ND, ICMPv6, VRRP, DHCPv6 Client, etc.";
              }
          }
      }
  }

  grouping router-id {
      description
          "This grouping provides router ID.";
      leaf router-id {
          type uint32;  // yang:dotted-quad
          description
            "A 32-bit number in the form of a dotted quad that is
             used by some routing protocols identifying a router.";
          reference
              "RFC 2328: OSPF Version 2.";
      }
  }

  grouping oam-protocols {
      container oam-protocols {
          list oam-protocol {
              key "type";
              leaf type {
                  type identityref {
                      base oam-protocol-type;
                  }
                  mandatory true;
                  description
                      "The Operations, Administration, and
                       Maintenance (OAM) protocol type, e.g., BFD,
                       TWAMP, CFM, etc.";
              }
              description
                  "List of OAM protocols configured for a
                   networking instance.";
          }
          description
              "Container for list of OAM protocols configured for a
                networking instance.";
      }
      description
          "Grouping for OAM protocols configured for a
           networking instance.";
  }

  grouping mpls {
    description
        "Grouping for MPLS and TE configuration configured for
         a networking-instance.";
    container mpls {
      description
          "Container for MPLS and TE configuration for a
           networking-instance.";
      container global {
          description "Global MPLS configuration";
      }
      list mpls-protocol {
          key "type";
          description
              "List of MPLS protocols configured for a
               networking instance.";
          leaf type {
              type identityref {
                  base mpls-protocol-type;
              }
              mandatory true;
              description
                  "MPLS and Traffic Engineering protocol type,
                   MPLS static, LDP, RSVP TE, etc.";
          }
      }
    }
  }

  grouping networking-instance-policy {
    description
        "Networking instance policies such as route
         distinguisher, route targets, VPLS ID and neighbor,
         Ethernet ID, etc. ";
    reference
        "RFC 4364 - BGP/MPLS Virtual Private Networks (VPNs)
         RFC 6074 - Provisioning, Auto-Discovery, and Signaling
              in Layer 2 Virtual Private Networks (L2VPNs)
         RFC 7432 - BGP MPLS-Based Ethernet VPN";
    container networking-instance-policy {
        description "Networking Instance Policy -- details TBD";
    }
  }

  grouping control-plane-protocols {
      description
          "Grouping for control plane protocols configured for
           a networking-instance";
      container control-plane-protocols {
          description
              "Container for control plane protocols configured for
               a networking instance.";
          list control-plane-protocol {
              key "type";
              description
                  "List of control plane protocols configured for
                   a networking instance.";
              leaf type {
                  type identityref {
                      base control-plane-protocol-type;
                  }
                  mandatory true;
                  description
                      "The control plane protocol type, e.g., BGP,
                       OSPF IS-IS, etc";
              }
              container policy {
                  description
                      "Protocol specific policy,
                      reusing [RTG-POLICY]";
              }
          }
      }
  }

  grouping ribs {
    description
      "Routing Information Bases (RIBs) supported by a
       networking-instance";
    container ribs {
        description
            "RIBs supported by a networking-instance";
        list rib {
            key "name";
            min-elements "1";
            description
                "Each entry represents a RIB identified by the
               'name' key. All routes in a RIB must belong to the
                same address family.

                For each routing instance, an implementation should
                provide one system-controlled default RIB for each
                supported address family.";
            leaf name {
                type string;
                description
                    "The name of the RIB.";
            }
            reference "draft-ietf-netmod-routing-cfg";
            leaf description {
                type string;
                description
                    "Description of the RIB";
            }
            // Note that there is no list of interfaces within
            container policy {
                description "Policy specific to RIB";
            }
        }
    }
  }

  grouping networking-services {
      description
          "Grouping for networking-services configured for
           a networking-instance.";
      container networking-services {
          description
              "Container for lst of networking services configured
               for a networking instance.";
          list networking-service {
              key "type";
              description
                  "List of networking services configured for a
                   networking instance.";
              leaf type {
                  type identityref {
                      base networking-service-type;
                  }
                  mandatory true;
                  description
                      "The networking services type supported within
                       a networking instance, e.g., NTP server, DNS
                       server, DHCP server, etc.";
              }
          }
      }
  }

  grouping oam-services {
    description "containers for features related to operations,
                 administration, and maintenance (OAM).";
    container oam-services {
      description "Commonly use OAM functions on devices";
      list oam-service {
          key "type";
          description
              "List of OAM services configured for a
               logical network element.";
          leaf type {
              type identityref {
                  base oam-service-type;
              }
              mandatory true;
                  description
                      "The OAM services type supported within
                       a logical networking element, e.g., SNMP.";
          }
      }
    }
  }

  grouping system-services {
    description "Containers for system service models.";
    uses oam-services;
  }

  grouping system-aaa {
    description "AAA-related services";
    container aaa {
      description
          "Authentication, Authorization, and Accounting (AAA).";
      list aaa-service {
          key "type";
          description
              "List of AAA services configured for a
               logical network element.";
          leaf type {
              type identityref {
                  base aaa-service-type;
              }
              mandatory true;
                  description
                      "The AAA services type supported within
                       a logical networking element, e.g., RADIUS.";
          }
      }
    }
  }

  grouping system-management {
      description "System management for device or logical network
                 element";
      container system-management {
          description "System management for device or logical
                       network element";
          container system-management-global {
              description "System management - logical device
                           management with reuse of RFC 7317";
          }
          list system-management-protocol {
              key "type";
              leaf type {
                  type identityref {
                      base system-management-protocol-type;
                  }
                  mandatory true;
                  description
                      "NTP, DNS, Syslog, ssh, TACAC+, NETCONF, etc.";
              }
              description "List of system management protocol
                           configured for a logical networking
                           element.";
          }
      }
  }

  grouping ietf-acl {
      description "Packet Access Control Lists (ACLs) as specified
                   in draft-ietf-netmod-acl-model";
      container ietf-acl {
          description "ACLs and packet forwarding rules";
      }
  }

  grouping ietf-key-chain {
      description "Key chains as specified in
                   draft-acee-rtgwg-yang-key-chain;";
      container ietf-key-chain {
          description "Key chains";
      }
  }

  // top level device definition statements
  container info {
    description
      "Base system information.
      This container is for base system information, including
      device type (e.g., physical or virtual), model, serial no.,
      location, etc.";

    leaf device-type {
      //TODO: consider changing to an identity if finer grained
      // device type classification is envisioned
      type enumeration {
        enum PHYSICAL {
          description "physical or hardware device";
        }
        enum VIRTUAL {
          description "virtual or software device";
        }
      }
      description
        "Type of the device, e.g., physical or virtual.  This node
        may be used to activate other containers in the model";
    }
  }

  container hardware {
    description
      "Hardware / vendor -specific data relevant to the platform.
      This container is an anchor point for platform-specific
      configuration and operational state data.  It may be further
      organized into chassis, line cards, ports, etc.  It is
      expected that vendor or platform-specific augmentations
      would be used to populate this part of the device model";
  }

  container qos {
    description "QoS features, for example policing, shaping, etc.";
  }

  container logical-network-elements {
    description "Network devices may support multiple logical
                 network instances";

    list logical-network-element {
      key network-element-id;
      description "List of logical network elements";
      leaf network-element-id {
        type uint8; // expect a small number of logical routers
        description "Device-wide unique identifier for the
                     Logical Network Element (LNE). The LNE with
                     the network-element-id of 0 is the default
                     and has system management responsibility
                     and visibility for the entire device.";
      }
      leaf network-element-name {
        type string;
        description "Descriptive name for the logical network
                     element";
      }
      leaf default-networking-instance-name {
        type string;
        description "Specification of the networking instance to
                     use for management connectivity";
      }
      uses system-management;
      uses ietf-acl;
      uses ietf-key-chain;
      container networking-instances {
          description "Networking instances each of which have
                       an independent IP/IPv6 addressing space
                       and protocol instantiations. For layer 3,
                       this consistent with the routing-instance
                       definition in ietf-routing";
          reference "draft-ietf-netmod-routing-cfg";
          list networking-instance {
              key networking-instance-name;
              description "List of networking-instances";
              leaf networking-instance-name {
                  type string;
                  description "logical network element scoped
                               identifier for the networking
                               instance";
              }
              leaf type {
                  type identityref {
                      base networking-instance;
                  }
                  description
                      "The networking instance type -- details TBD
                       Likely types include core, L3-VRF, VPLS,
                       L2-cross-connect, L2-VSI, etc.";
              }
              leaf enabled {
                  type boolean;
                  default "true";
                  description
                    "Flag indicating whether or not the networking
                     instance is enabled.";
              }
              uses router-id {
                  description
                      "Router ID for networking instances";
              }
              leaf description {
                  type string;
                  description
                    "Description of the networking instance
                    and its intended purpose";
              }
              // Note that there is no list of interfaces within
              // the networking-instance
              uses oam-protocols;
              uses networking-instance-policy;
              uses control-plane-protocols;
              uses ribs;
              uses mpls;
              uses networking-services;
          }
      }
    }
  }

  // augment statements
  augment "/if:interfaces/if:interface" {
    description
        "Add a node for the identification of the logical network
        element associated with an interface. Applies to interfaces
        that can be assigned on a per logical network element basis.
        A <TBD> error is returned when the interface type cannot be
        assigned.";

    leaf bind-network-element-id {
      type uint8;
      description
        "Logical network element ID to which interface is bound";
    }
  }

  augment "/if:interfaces/if:interface" {
    description
        "Add a node for the identification of the logical networking
        instance (which is within the interface's identified logical
        network element) associated with the IP information
        configured on an interface";

    leaf bind-networking-instance-name {
      type string;
      description
        "Networking Instance to which an interface is bound";
    }
  }

  augment "/if:interfaces/if:interface/ip:ipv4" {
    description
        "Add a node for the identification of the logical networking
        instance (which is within the interface's identified logical
        network element) associated with the IP information
        configured on an interface";

    leaf bind-networking-instance-name {
      type string;
      description
        "Networking Instance to which IPv4 interface is bound";

    }
  }

  augment "/if:interfaces/if:interface/ip:ipv6" {
    description
        "Add a node for the identification of the logical networking
        instance (which is within the interface's identified logical
        network element) associated with the IP information
        configured on an interface";

    leaf bind-networking-instance-name {
      type string;
      description
        "Networking Instance to which IPv6 interface is bound";

    }
  }

  // rpc statements

  // notification statements

}
